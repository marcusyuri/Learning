module openconfig-gribi {
  yang-version "1";

  prefix "oc-gribi";

  namespace "http://openconfig.net/yang/gribi";

  import openconfig-extensions { prefix oc-ext; }
  import openconfig-system-grpc { prefix oc-sys-grpc; }

  organization
    "OpenConfig Working Group";

  contact
    "www.openconfig.net";

  description
    "This module defines a set of exdtensions that provide gRIBI (the gRPC
    RIB Interface) specific extensions to the OpenConfig data models.
    Specifically, the parameters for the configuration of the service, and
    configuration and state are added.

    The gRIBI protobufs and documentation are published at
    https://github.com/openconfig/gribi.";

  oc-ext:openconfig-version "0.1.0";

  revision 2021-04-06 {
    description
      "Initial revision.";
    reference "0.1.0";
  }

  identity GRIBI {
    base "oc-sys-grpc:GRPC_SERVICE";
    description
      "gRIBI: gRPC Routing Information Base Interface";
  }
}
