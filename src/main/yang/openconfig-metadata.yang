module openconfig-metadata {

  yang-version "1";

  namespace "http://openconfig.net/yang/openconfig-metadata";
  prefix "oc-metadata";

  import openconfig-extensions { prefix oc-ext; }

  organization
    "OpenConfig working group";

  contact
    "OpenConfig working group
    www.openconfig.net";

  description
    "This module defines metadata types that are defined by
    the OpenConfig group.";

  oc-ext:openconfig-version "0.1.0";

  revision 2020-08-06 {
    description
      "Initial revision.";
    reference "0.1.0";
  }

  extension annotation {
    argument name;
    description
      "This extension allows for defining metadata annotations in
       YANG modules. The 'md:annotation' statement can appear only at
       the top level of a YANG module.

       The argument of the 'md:annotation' statement defines the name
       of the annotation. Syntactically it is a YANG identifier as
       defined in RFC 6020bis, sec. 6.2.

       An annotation defined with this extension statement inherits
       the namespace and other context from the YANG module in which
       it is defined.

       Data type of the annotation value is specified in the same way
       as for a leaf data node using the 'type' statement.

       Semantics of the annotation and other documentation can be
       specified using the following standard YANG substatements (all
       are optional): 'description', 'if-feature', 'reference',
       'status', and 'units'.

       A server announces support for a particular annotation by
       including the module in which the annotation is defined among
       the advertised YANG modules (e.g., in NETCONF hello message or
       yang-library). The annotation then can be attached to any
       instance of data node defined in any YANG module that is
       advertised by the server.

       XML and JSON encoding of annotations is defined in
       RFC XXXX.";
  }

  oc-metadata:annotation protobuf-metadata {
    type binary {
      length "0..1048000";
    }
    description
      "A binary marshalled protobuf message, with a size that does not exceed
      1MiB containing metadata related to the element of the data tree at which
      the metadata annotation is used.

      It is expected that this metadata can be both written and read by a
      client - and that the value is persistent across system restarts.

      A client using this metadata extension should ensure that it is able
      to unmarshal its contents successfully. It is suggested that the
      payload should be a protobuf.Any message, which has corresponding
      type information such that information as to the intended structure
      can be retrieved by any reader.";
  }
}
