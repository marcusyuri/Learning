module openconfig-security-ipsec {

  yang-version "1";
  namespace "http://openconfig.net/yang/security/ipsec";
  prefix "oc-sec-ipsec";

  import openconfig-inet-types {
    prefix oc-inet;
  }
  import openconfig-yang-types {
    prefix oc-yang;
  }
  import openconfig-extensions {
    prefix oc-ext;
  }
  import openconfig-network-instance {
    prefix oc-ni;
  }
  import openconfig-interfaces {
    prefix oc-if;
  }
  import openconfig-security {
    prefix oc-sec;
  }
  import openconfig-security-types {
    prefix oc-sec-types;
  }
  import openconfig-security-ike {
    prefix oc-sec-ike;
  }

// meta
  organization
    "OpenConfig working group";

  contact
    "OpenConfig working group
     netopenconfig@googlegroups.com";

  description
    "This module defines configuration and operational state for IPSec.";

  oc-ext:openconfig-version "0.1.0";

  revision 2025-12-03 {
    description
      "Initial ipsec model covering ipsec telemetry.";
    reference
      "0.1.0";
  }

// OpenConfig specific extensions for module metadata.
  oc-ext:regexp-posix;
  oc-ext:catalog-organization "openconfig";
  oc-ext:origin "openconfig";

  grouping security-ipsec-top {
    description
      "Top level container for IPSec.";
    container ipsec {
      description
        "Container for ipsec";
      container ipv4 {
        description
          "Container for ipv4";
        container connections {
          description
            "Container for connections";
          list connection {
            key "name";
            config false;
            description
              "List of IPsec connection entries";
            leaf name {
              type leafref {
                path "../state/name";
              }
              mandatory true;
              description
                "Reference to the IPsec connection name.";
            }

            container state {
              config false;
              description
                "State data";

              leaf name {
                type string;
                mandatory true;
                description
                  "The name of the IPsec connection.";
              }

              leaf profile-name {
                // TODO this could be a leafref to a configured profile such as
                // security/ipsec/profiles/profile/config/name
                type string;
                mandatory true;
                description
                  "Reference to the configured IPsec profile name used by this connection.";
              }

              leaf tunnel-interface {
                type leafref {
                  path "/oc-if:interfaces/oc-if:interface/oc-if:name";
                }
                mandatory true;
                description
                  "Reference to the associated tunnel interface name.";
              }

              leaf status {
                type identityref {
                  base oc-sec-types:CONNECTION_STATUS;
                }
                mandatory true;
                description
                  "The current status of the IPsec connection.";
              }

              leaf local-address {
                type oc-inet:ipv4-address;
                mandatory true;
                description
                  "The local IP address of the IPsec connection.";
              }

              leaf remote-address {
                type oc-inet:ipv4-address;
                mandatory true;
                description
                  "The remote peer's IP address of the IPsec connection.";
              }

              leaf connection-uptime {
                type oc-yang:date-and-time;
                mandatory true;
                description
                  "The timestamp indicating when the connection was last active.";
              }

              leaf next-sa-rekey-time {
                type oc-yang:date-and-time;
                mandatory true;
                description
                  "The timestamp for the next scheduled rekey event for the Child SA within this connection.";
              }

              leaf error {
                type string;
                mandatory true;
                description
                  "The error occurred on the IPsec connection.";
              }

              container counters {
                description
                  "Container for counters";
                leaf input-bytes {
                  type oc-yang:counter64;
                  mandatory true;
                  description
                    "Total input bytes received on the IPsec connection.";
                }

                leaf input-packets {
                  type oc-yang:counter64;
                  mandatory true;
                  description
                    "Total input packets received on the IPsec connection.";
                }

                leaf output-bytes {
                  type oc-yang:counter64;
                  mandatory true;
                  description
                    "Total output bytes sent on the IPsec connection.";
                }

                leaf output-packets {
                  type oc-yang:counter64;
                  mandatory true;
                  description
                    "Total output packets sent on the IPsec connection.";
                }

                leaf replay-failure {
                  type oc-yang:counter64;
                  mandatory true;
                  description
                    "Count of packets dropped due to anti-replay failures during decryption.";
                }

                leaf integrity-failure {
                  type oc-yang:counter64;
                  mandatory true;
                  description
                    "Count of packets dropped due to integrity check failures during decryption.";
                }

                leaf encryption-failure {
                  type oc-yang:counter64;
                  mandatory true;
                  description
                    "Count of packets dropped due to encryption failures.";
                }
              }
            }

            container ike-security-associations {
              description
                "Container for ike-security-associations";
              list ike-security-association {
                key "initiator-spi responder-spi remote-address local-address";
                description
                  "List of security-association entries";

                leaf initiator-spi {
                  type leafref {
                    path "../state/initiator-spi";
                  }
                  mandatory true;
                  description
                    "Reference to the IKE SA's SPI.";
                }

                leaf responder-spi {
                  type leafref {
                    path "../state/responder-spi";
                  }
                  mandatory true;
                  description
                    "Reference to the IKE SA's SPI.";
                }

                leaf remote-address {
                  type leafref {
                    path "../state/remote-address";
                  }
                  mandatory true;
                  description
                    "Reference to the IKE SA's remote address.";
                }

                leaf local-address {
                  type leafref {
                    path "../state/local-address";
                  }
                  mandatory true;
                  description
                    "Reference to the IKE SA's local address.";
                }
                container state {
                  description
                    "Container for IKE security association state data.";
                  leaf initiator-spi {
                    type leafref {
                      path "../../../../../../../../oc-sec-ike:ike/oc-sec-ike:ike-sa/oc-sec-ike:ipv4/oc-sec-ike:security-associations/oc-sec-ike:security-association/oc-sec-ike:initiator-spi";
                    }
                    mandatory true;
                    description
                      "Reference to the IKE SA's SPI.";
                  }
                  leaf responder-spi {
                    type leafref {
                      path "../../../../../../../../oc-sec-ike:ike/oc-sec-ike:ike-sa/oc-sec-ike:ipv4/oc-sec-ike:security-associations/oc-sec-ike:security-association/oc-sec-ike:responder-spi";
                    }
                    mandatory true;
                    description
                      "Reference to the IKE SA's SPI.";
                  }
                  leaf remote-address {
                    type leafref {
                      path "../../../../../../../../oc-sec-ike:ike/oc-sec-ike:ike-sa/oc-sec-ike:ipv4/oc-sec-ike:security-associations/oc-sec-ike:security-association/oc-sec-ike:remote-address";
                    }
                    mandatory true;
                    description
                      "Reference to the IKE SA's remote address.";
                  }
                  leaf local-address {
                    type leafref {
                      path "../../../../../../../../oc-sec-ike:ike/oc-sec-ike:ike-sa/oc-sec-ike:ipv4/oc-sec-ike:security-associations/oc-sec-ike:security-association/oc-sec-ike:local-address";
                    }
                    mandatory true;
                    description
                      "Reference to the IKE SA's local address.";
                  }
                }
              }
            }

            container child-security-associations {
              description
                "Container for child-security-associations.";
              list child-security-association {
                key "spi destination-address protocol";
                description
                  "List of security-association entries.";
                leaf spi {
                  description
                    "Reference to the Security Parameter Index (SPI) for child
                     security associations list key.";
                  type leafref {
                    path "../state/spi";
                  }
                }
                leaf destination-address {
                  description
                    "Reference to destination IP address for child security
                     associations list key.";
                  type leafref {
                    path "../state/destination-address";
                  }
                }
                leaf protocol {
                  description
                    "Reference to protocol for child security associations
                     list key.";
                  type leafref {
                    path "../state/protocol";
                  }
                }
                container state {
                  description
                    "Container for state of child-security-associations.";
                  leaf spi {
                    type leafref {
                      path "../../../../../../../../oc-sec-ike:ike/oc-sec-ike:child-sa/oc-sec-ike:ipv4/oc-sec-ike:security-associations/oc-sec-ike:security-association/oc-sec-ike:spi";
                    }
                    mandatory true;
                    description
                      "Reference to the Child SA's SPI.";
                  }

                  leaf destination-address {
                    type leafref {
                      path "../../../../../../../../oc-sec-ike:ike/oc-sec-ike:child-sa/oc-sec-ike:ipv4/oc-sec-ike:security-associations/oc-sec-ike:security-association/oc-sec-ike:destination-address";
                    }
                    mandatory true;
                    description
                      "Reference to the Child SA's destination address.";
                  }

                  leaf protocol {
                    type leafref {
                      path "../../../../../../../../oc-sec-ike:ike/oc-sec-ike:child-sa/oc-sec-ike:ipv4/oc-sec-ike:security-associations/oc-sec-ike:security-association/oc-sec-ike:protocol";
                    }
                    mandatory true;
                    description
                      "Reference to the Child SA's protocol.";
                  }
                }
              }
            }
          }
        }
      }

      container ipv6 {
        description
          "Container for ipv6";
        container connections {
          description
            "Container for connections";
          list connection {
            key "name";
            config false;
            description
              "List of IPsec connection entries";
            leaf name {
              type leafref {
                path "../state/name";
              }
              mandatory true;
              description
                "Reference to the IPsec connection name";
            }

            container state {
              config false;
              description
                "State container";

              leaf name {
                type string;
                mandatory true;
                description
                  "The name of the IPsec connection.";
              }

              leaf profile-name {
                // TODO this could be a leafref to a configured profile such as
                // security/ipsec/profiles/profile/config/name
                type string;
                mandatory true;
                description
                  "Reference to the configured IPsec profile name used by this
                   connection.";
              }

              leaf tunnel-interface {
                type leafref {
                  path "/oc-if:interfaces/oc-if:interface/oc-if:name";
                }
                mandatory true;
                description
                  "Reference to the associated tunnel interface name.";
              }

              leaf status {
                type identityref {
                  base oc-sec-types:CONNECTION_STATUS;
                }
                mandatory true;
                description
                  "The current status of the IPsec connection.";
              }

              leaf local-address {
                type oc-inet:ipv6-address;
                mandatory true;
                description
                  "The local IP address of the IPsec connection.";
              }

              leaf remote-address {
                type oc-inet:ipv6-address;
                mandatory true;
                description
                  "The remote peer's IP address of the IPsec connection.";
              }

              leaf connection-uptime {
                type oc-yang:date-and-time;
                mandatory true;
                description
                  "The timestamp indicating when the connection was last
                   active.";
              }

              leaf next-sa-rekey-time {
                type oc-yang:date-and-time;
                mandatory true;
                description
                  "The timestamp for the next scheduled rekey event for the
                   Child SA within this connection.";
              }

              leaf error {
                type string;
                mandatory true;
                description
                  "The error occurred on the IPsec connection.";
              }

              container counters {
                description
                  "Container for counters";
                leaf input-bytes {
                  type oc-yang:counter64;
                  mandatory true;
                  description
                    "Total input bytes received on the IPsec connection.";
                }

                leaf input-packets {
                  type oc-yang:counter64;
                  mandatory true;
                  description
                    "Total input packets received on the IPsec connection.";
                }

                leaf output-bytes {
                  type oc-yang:counter64;
                  mandatory true;
                  description
                    "Total output bytes sent on the IPsec connection.";
                }

                leaf output-packets {
                  type oc-yang:counter64;
                  mandatory true;
                  description
                    "Total output packets sent on the IPsec connection.";
                }

                leaf replay-failure {
                  type oc-yang:counter64;
                  mandatory true;
                  description
                    "Count of packets dropped due to anti-replay failures during decryption.";
                }

                leaf integrity-failure {
                  type oc-yang:counter64;
                  mandatory true;
                  description
                    "Count of packets dropped due to integrity check failures during decryption.";
                }

                leaf encryption-failure {
                  type oc-yang:counter64;
                  mandatory true;
                  description
                    "Count of packets dropped due to encryption failures.";
                }
              }
            }

            container ike-security-associations {
              description
                "Container for ike-security-associations";
              list ike-security-association {
                key "initiator-spi responder-spi remote-address local-address";
                description
                  "List of security-association entries";
                leaf initiator-spi {
                  type leafref {
                    path "../state/initiator-spi";
                  }
                  mandatory true;
                  description
                    "Reference to the IKE SA's SPI.";
                }
                leaf responder-spi {
                  type leafref {
                    path "../state/responder-spi";
                  }
                  mandatory true;
                  description
                    "Reference to the IKE SA's SPI.";
                }

                leaf remote-address {
                  type leafref {
                    path "../state/remote-address";
                  }
                  mandatory true;
                  description
                    "Reference to the IKE SA's remote address.";
                }

                leaf local-address {
                  type leafref {
                    path "../state/local-address";
                  }
                  mandatory true;
                  description
                    "Reference to the IKE SA's local address.";
                }
                container state {
                  description
                    "Container for IKE security association state data.";
                  leaf initiator-spi {
                    type leafref {
                      path "../../../../../../../../oc-sec-ike:ike/oc-sec-ike:ike-sa/oc-sec-ike:ipv6/oc-sec-ike:security-associations/oc-sec-ike:security-association/oc-sec-ike:initiator-spi";
                    }
                    mandatory true;
                    description
                      "Reference to the IKE SA's SPI.";
                  }
                  leaf responder-spi {
                    type leafref {
                      path "../../../../../../../../oc-sec-ike:ike/oc-sec-ike:ike-sa/oc-sec-ike:ipv6/oc-sec-ike:security-associations/oc-sec-ike:security-association/oc-sec-ike:responder-spi";
                    }
                    mandatory true;
                    description
                      "Reference to the IKE SA's SPI.";
                  }

                  leaf remote-address {
                    type leafref {
                      path "../../../../../../../../oc-sec-ike:ike/oc-sec-ike:ike-sa/oc-sec-ike:ipv6/oc-sec-ike:security-associations/oc-sec-ike:security-association/oc-sec-ike:remote-address";
                    }
                    mandatory true;
                    description
                      "Reference to the IKE SA's remote address.";
                  }

                  leaf local-address {
                    type leafref {
                      path "../../../../../../../../oc-sec-ike:ike/oc-sec-ike:ike-sa/oc-sec-ike:ipv6/oc-sec-ike:security-associations/oc-sec-ike:security-association/oc-sec-ike:local-address";
                    }
                    mandatory true;
                    description
                      "Reference to the IKE SA's local address.";
                  }
                }
              }
            }

            container child-security-associations {
              description
                "Container for child-security-associations";
              list child-security-association {
                key "spi destination-address protocol";
                description
                  "List of security-association entries";
                leaf spi {
                  description
                    "Reference to Security Parameter Index for child security
                     associations list key.";
                  type leafref {
                    path "../state/spi";
                  }
                }
                leaf destination-address {
                  description
                    "Reference to destination IP address for child security
                     associations list key.";
                  type leafref {
                    path "../state/destination-address";
                  }
                }
                leaf protocol {
                  description
                    "Reference to protocol for child security associations list
                     key.";
                  type leafref {
                    path "../state/protocol";
                  }
                }
                container state {
                  description
                    "State for child -security-association entries";
                  leaf spi {
                    type leafref {
                      path "../../../../../../../../oc-sec-ike:ike/oc-sec-ike:child-sa/oc-sec-ike:ipv6/oc-sec-ike:security-associations/oc-sec-ike:security-association/oc-sec-ike:spi";
                    }
                    mandatory true;
                    description
                      "Reference to the Child SA's SPI.";
                  }

                  leaf destination-address {
                    type leafref {
                      path "../../../../../../../../oc-sec-ike:ike/oc-sec-ike:child-sa/oc-sec-ike:ipv6/oc-sec-ike:security-associations/oc-sec-ike:security-association/oc-sec-ike:destination-address";
                    }
                    mandatory true;
                    description
                      "Reference to the Child SA's destination address.";
                  }

                  leaf protocol {
                    type leafref {
                      path "../../../../../../../../oc-sec-ike:ike/oc-sec-ike:child-sa/oc-sec-ike:ipv6/oc-sec-ike:security-associations/oc-sec-ike:security-association/oc-sec-ike:protocol";
                    }
                    mandatory true;
                    description
                      "Reference to the Child SA's protocol.";
                  }
                }
              }
            }
          }
        }
      }
    }
  }

  // augment statements
  augment "/oc-ni:network-instances/oc-ni:network-instance/oc-sec:security" {
    description
      "Add security grouping to the network-instances tree.";

    uses security-ipsec-top;
  }
// rpc statements notification statements
}
